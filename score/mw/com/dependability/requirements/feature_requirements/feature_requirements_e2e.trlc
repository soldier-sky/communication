/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

ScoreReq.FeatReq SupportForEndToEndProtection {
    description = "The communication framework shall support End-to-End (E2E) protection of transmitted data to detect corruption, loss (gap in the received sample sequence ), repetition, and reordering between communication partners of the same or different criticality levels."
    safety = ScoreReq.Asil.B
    derived_from = [ Communication.SystemSafeCommunication@1, Communication.InterProcessCommunication@1 ]
    version = 1
}

ScoreReq.FeatReq E2EProtectionForEvents {
    description = "The communication framework shall support E2E protection for periodically or semi-periodically transmitted events and fields."
    safety = ScoreReq.Asil.B
    note = "E2E protection assumes a receiver with an expectation of regular data reception; communication paradigms without such an expectation (e.g. plain signal-based communication) are out of scope for this capability."
    derived_from = [ Communication.SystemSafeCommunication@1, Communication.SystemSupportForDataDrivenArchitecture@1 ]
    version = 1
}

ScoreReq.FeatReq E2EProtectionForMethods {
    description = "The communication framework shall support E2E protection for service method request and response communication, limited to a single dedicated server per protected method (N:1 client-to-server)."
    safety = ScoreReq.Asil.B
    note = "Client-specific failure modes (e.g. repetition or insertion originating from one of several clients) are only detectable when a session/client-aware profile variant is used; the plain profile variant provides no a priori knowledge of the requesting client."
    derived_from = [ Communication.SystemSafeCommunication@1, Communication.SystemSupportForRequestDrivenArchitecture@1 ]
    version = 1
}

ScoreReq.FeatReq E2EStatusReportingToApplication {
    description = "The communication framework shall report the outcome of E2E supervision as a communication-level status delivered to the consuming application together with each sample, without prescribing what action the application takes on that status."
    safety = ScoreReq.Asil.B
    derived_from = [ Communication.SystemSafeCommunication@1 ]
    version = 1
}

ScoreReq.FeatReq MixedCriticalityE2ESupervision {
    description = "The communication framework shall allow communication partners of different criticality levels to independently consume the same E2E-protected event, each evaluating E2E status relevant to its own criticality."
    safety = ScoreReq.Asil.B
    derived_from = [ Communication.SystemSafeCommunication@1, Communication.InterProcessCommunication@1 ]
    version = 1
}

ScoreReq.FeatReq E2EUsageErrorsDistinctFromCommunicationFaultStatus {
    description = "The communication framework shall report an E2E API usage or configuration error (e.g. a null required argument or an out-of-range input) through a channel distinct from the per-sample communication-fault check status, so that it is surfaced as a programming or configuration defect rather than as a runtime check-status value such as an error or repeated-sample result."
    safety = ScoreReq.Asil.B
    note = "The function-level return codes for a protect/forward/check call are distinct from the per-sample check status; conflating the two would collapse a usage-error channel and a communication-fault channel into one."
    derived_from = [Communication.SystemErrorHandling@1, Communication.SystemSafeCommunication@1]
    version = 1
}

ScoreReq.FeatReq E2EErrorClassificationPreservesMasqueradingAndInsertionDetection {
    description = "The communication framework's E2E error status shall preserve detection of masquerading and insertion faults, performed via the Data ID and CRC checks, and not reduce the exposed error classification to counter-based faults (loss, repetition, reordering) alone."
    safety = ScoreReq.Asil.B
    note = "Counter-based checks alone cannot detect a correctly-sequenced but wrongly-addressed or corrupted sample; Data ID and CRC checks cover a distinct fault class that must remain visible in the reported error, not just sequence-related faults."
    derived_from = [Communication.SystemSafeCommunication@1]
    version = 1
}
