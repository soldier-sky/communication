/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "E2E" {

        section "Skeleton_Side_Protect_State" {

            ScoreReq.CompReq SkeletonEventBindingOwnsE2EProtectContext {
                description = """{{SkeletonEventBinding}} shall own exactly one E2E protect context (sender counter) per {{SkeletonEvent}} or {{SkeletonField}} instance for which E2E protection is enabled, and shall invoke {{ProtectMessage}} on it directly."""
                safety = ScoreReq.Asil.B
                note = "The binding is the only party holding the fully-assembled wire buffer/slot at the point ProtectMessage() must run, so the counter lives in the binding rather than in SkeletonEventBase; only the reusable CRC/counter algorithm is shared, binding-independent code."
                derived_from = [Communication.E2EProtectionForEvents@1]
                version = 1
            }

            ScoreReq.CompReq E2EProtectContextNotReplicatedPerConsumer {
                description = """The E2E protect context owned by a {{SkeletonEventBinding}} shall be shared across all consumers of the corresponding event or field; it shall not be replicated or reset per subscribing {{ProxyEvent}} or {{ProxyField}}."""
                safety = ScoreReq.Asil.B
                note = "One event stream can be delivered to many consumers (multicast/pub-sub); replicating protect state per consumer would require a distinct frame per subscriber, defeating event distribution."
                derived_from = [Communication.E2EProtectionForEvents@1, Communication.MixedCriticalityE2ESupervision@1]
                version = 1
            }

            ScoreReq.CompReq E2EProtectionInvokedInsideBindingSend {
                description = """{{SkeletonEventBinding}} shall invoke E2E protection internally, as part of its own {{Send}} implementation, directly on the buffer or slot it already owns, without receiving precomputed E2E header bytes from the binding-independent layer."""
                safety = ScoreReq.Asil.B
                note = "The binding already owns every byte the CRC needs to cover (its own transport-specific prefix, the reserved header region, and the payload), so ProtectMessage() runs as a single in-place call with no cross-layer buffer handoff; SkeletonEventBase::Send()'s app-facing signature is unaffected."
                derived_from = [Communication.E2EProtectionForEvents@1]
                version = 1
            }

            ScoreReq.CompReq BindingIndependentLayerHasNoE2EHeaderVisibility {
                description = """The binding-independent layer shall neither construct, hold, nor pass E2E header bytes to {{SkeletonEventBinding}}; the E2E header shall remain entirely internal to the binding, invisible to the application and to generated code."""
                safety = ScoreReq.Asil.B
                derived_from = [Communication.E2EProtectionForEvents@1]
                version = 1
            }

        }

    }

}
