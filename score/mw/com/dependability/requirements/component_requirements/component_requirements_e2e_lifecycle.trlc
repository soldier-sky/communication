/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "E2E" {

        section "Context_Lifecycle" {

            ScoreReq.CompReq E2ECheckContextResetOnSubscriptionReestablishment {
                description = """{{ProxyEventBinding}} shall reset the E2E check context (last accepted counter, CRC library context) of a consuming {{ProxyEvent}} or {{ProxyField}} instance whenever its subscription transitions from not-subscribed back to subscribed."""
                safety = ScoreReq.Asil.B
                note = "The binding owns the check context and already tracks this transition internally for its own subscription-state purposes (e.g. LoLa's SubscriptionStateMachine), so no signal from the binding-independent layer is required. Without this reset, valid post-reconnection frames could be interpreted as a sequence error."
                derived_from = [Communication.E2EProtectionForEvents@1]
                version = 1
            }

            ScoreReq.CompReq E2EProtectContextResetOnServiceReoffer {
                description = """{{SkeletonEventBinding}} shall reset the E2E protect context (sender counter) of a {{SkeletonEvent}} or {{SkeletonField}} instance whenever the corresponding service instance is re-offered after having stopped offering."""
                safety = ScoreReq.Asil.B
                note = "The protect context is shared across all consumers of the event or field (see E2EProtectContextNotReplicatedPerConsumer); the binding already owns the service-offer lifecycle hooks (OfferService()/StopOfferService()) that bound this reset, so no cross-layer signal is required."
                derived_from = [Communication.E2EProtectionForEvents@1]
                version = 1
            }

            ScoreReq.CompReq E2EHealthContextResetOnSubscriptionStateChangeSignal {
                description = """{{ProxyEventBase}} shall reset the E2E historical-health context of a consuming {{ProxyEvent}} or {{ProxyField}} instance whenever the binding reports, via the existing subscription-state-change signal, that the subscription transitioned from not-subscribed back to subscribed."""
                safety = ScoreReq.Asil.B
                note = "The historical-health context has no wire-format dependency and stays binding-independent, but still needs to know when communication continuity was intentionally broken; otherwise valid post-restart frames could be misread as sequence errors and drive historical_health toward kError even though the channel was correctly re-established. This reuses the existing ProxyEventBindingBase::GetSubscriptionState()/SetSubscriptionStateChangeHandler() callback; no new binding interface is required."
                derived_from = [Communication.E2EProtectionForEvents@1]
                version = 1
            }

            ScoreReq.CompReq E2EContextResetUsesExistingSubscriptionStateSignal {
                description = """Resetting of the E2E protect and check contexts shall be performed internally by the binding using its own service-offering and subscription-state lifecycle hooks; resetting of the E2E historical-health context shall be performed by the binding-independent layer using the existing subscription-state-change signal reported by the binding; neither reset shall require additional binding-specific support beyond what is already used for subscription-state and service-offering purposes."""
                safety = ScoreReq.Asil.B
                derived_from = [Communication.E2EProtectionForEvents@1]
                version = 1
            }

        }

    }

}
