/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "E2E" {

        section "Proxy_Side_Check_State" {

            ScoreReq.CompReq ProxyEventBindingOwnsE2ECheckContext {
                description = """{{ProxyEventBinding}} shall own exactly one E2E check context (last accepted counter, CRC library context) per consuming {{ProxyEvent}} or {{ProxyField}} instance for which data-integrity or sequence checking is enabled, and shall invoke {{CheckMessage}} on it directly."""
                safety = ScoreReq.Asil.B
                note = "The check context is meaningless without the wire-format knowledge the binding already has (last accepted counter, CRC context), so it lives in the binding rather than in ProxyEventBase; see ProxyEventBaseOwnsE2EHealthContext for the binding-independent counterpart."
                derived_from = [Communication.E2EProtectionForEvents@1, Communication.MixedCriticalityE2ESupervision@1]
                version = 1
            }

            ScoreReq.CompReq ProxyEventBaseOwnsE2EHealthContext {
                description = """{{ProxyEventBase}} shall own exactly one E2E historical-health context per consuming {{ProxyEvent}} or {{ProxyField}} instance for which historical-health tracking is enabled, and shall not itself invoke {{CheckMessage}}."""
                safety = ScoreReq.Asil.B
                note = "The historical-health context has no wire-format dependency; it only interprets the DataIntegrityStatus/SequenceStatus pair already computed by the binding's ProxyEventBinding."
                derived_from = [Communication.E2EProtectionForEvents@1, Communication.MixedCriticalityE2ESupervision@1]
                version = 1
            }

            ScoreReq.CompReq E2ECheckInvokedOnlyWhenNewSamplePresent {
                description = """{{ProxyEventBinding}} shall invoke {{CheckMessage}} only for a call to {{GetNewSamples}} that actually delivers a new sample, and shall not synthesize a check result for a cycle where no new sample was received."""
                safety = ScoreReq.Asil.B
                note = "mw::com's reactive, event-driven consumption model has no periodic invocation-cadence contract for GetNewSamples(); a cycle where nothing new arrived has nothing for the check function to evaluate, so no empty-cycle result is produced and none is fed to historical-health tracking."
                derived_from = [Communication.E2EProtectionForEvents@1]
                version = 1
            }

            ScoreReq.CompReq E2EHealthContextUpdatedOnlyOnCheckedSample {
                description = """{{ProxyEventBase}} shall update the E2E historical-health context of a consuming {{ProxyEvent}} or {{ProxyField}} instance only on a {{GetNewSamples}} cycle in which the binding actually delivered and checked a new sample."""
                safety = ScoreReq.Asil.B
                note = "This is a narrower invocation contract than a periodic/windowed model would require, adopted deliberately since there is nothing to feed the counter on an empty cycle; no separate timer or scheduler component is needed to drive it."
                derived_from = [Communication.E2EProtectionForEvents@1]
                version = 1
            }

            ScoreReq.CompReq IndependentE2ESupervisionPerConsumer {
                description = """The E2E check outcome and historical-health state computed for one consuming {{ProxyEvent}} instance shall be independent of the samples observed or missed by any other consuming {{ProxyEvent}} instance of the same {{SkeletonEvent}}."""
                safety = ScoreReq.Asil.B
                derived_from = [Communication.MixedCriticalityE2ESupervision@1]
                version = 1
            }

        }

        section "Historical_Health_Tracking" {

            ScoreReq.CompReq HistoricalHealthStatusValues {
                description = """{{HistoricalHealthStatus}} owned by {{ProxyEventBase}} shall distinguish at least the following outcomes for a supervised {{Event}} or {{Field}}: {{kDisabled}}, {{kOk}}, and {{kError}}."""
                safety = ScoreReq.Asil.B
                derived_from = [Communication.E2EProtectionForEvents@1]
                version = 1
            }

            ScoreReq.CompReq HistoricalHealthHysteresisTransitions {
                description = """{{ProxyEventBase}} shall maintain a hysteresis error counter that is incremented by a configurable {{ErrorIncrement}} on a failed per-message check and decremented by a configurable {{OkDecrement}} on a passed one, clamped so it never drops below zero; {{HistoricalHealthStatus}} shall transition to {{kError}} once the counter reaches a configurable {{ErrorThreshold}} and shall return to {{kOk}} only once the counter drops to or below a configurable {{RecoveryThreshold}} that is less than or equal to {{ErrorThreshold}}."""
                safety = ScoreReq.Asil.B
                note = "The gap between ErrorThreshold and RecoveryThreshold is the hysteresis band, preventing the status from flapping on a single isolated failure or recovery. This replaces a fixed-cycle windowed state machine, which would otherwise require feeding an explicit result for every reception cycle including cycles where nothing new arrived."
                derived_from = [Communication.E2EProtectionForEvents@1]
                version = 1
            }

            ScoreReq.CompReq NoNewDataAloneDoesNotDegradeHistoricalHealth {
                description = """A {{GetNewSamples}} cycle that delivers no new sample shall not, by itself, change the {{HistoricalHealthStatus}} of a consuming {{ProxyEvent}} or {{ProxyField}} instance away from {{kOk}}."""
                safety = ScoreReq.Asil.B
                note = "Stall or dead-sender detection is out of scope for E2E historical-health tracking and remains the responsibility of mw::com's subscription/service-availability lifecycle (e.g. the subscription-state-change handler)."
                derived_from = [Communication.E2EProtectionForEvents@1]
                version = 1
            }

        }

    }

}
