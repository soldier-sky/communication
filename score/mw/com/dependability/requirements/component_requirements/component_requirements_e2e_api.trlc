/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

section "com" {

    section "E2E" {

        section "Public_API" {

            ScoreReq.CompReq E2EResultFieldValues {
                description = """{{E2EResult}} shall expose: a {{DataIntegrityStatus}} distinguishing at least {{kDisabled}}, {{kOk}}, and {{kError}}; a {{SequenceStatus}} distinguishing at least {{kDisabled}}, {{kOk}}, {{kOkGapWithinThreshold}}, {{kErrorRepeated}}, and {{kErrorGapExceedsThreshold}}; a {{HistoricalHealthStatus}} distinguishing at least {{kDisabled}}, {{kOk}}, and {{kError}}; and a {{Summary}} distinguishing at least {{kDisabled}}, {{kOk}}, {{kOkWithDisabledChecks}}, and {{kError}}."""
                safety = ScoreReq.Asil.B
                note = "data_integrity and sequence are kept as two independent per-sample fields rather than merged into one status value, since a masquerading/corruption fault and a loss/reorder fault are actionable differently by a consumer."
                derived_from = [Communication.E2EStatusReportingToApplication@1, Communication.E2EErrorClassificationPreservesMasqueradingAndInsertionDetection@1]
                version = 1
            }

            ScoreReq.CompReq SummaryIsDerivedFromOtherE2EResultFields {
                description = """{{Summary}} shall be computed only from the current {{DataIntegrityStatus}}, {{SequenceStatus}}, and {{HistoricalHealthStatus}} values carried by the same {{E2EResult}}, and shall not be independently settable."""
                safety = ScoreReq.Asil.B
                note = "A derived, non-independently-settable Summary cannot drift out of sync with the three fields it summarizes: kDisabled when all three are kDisabled, kError when any of them reports an error, and kOk/kOkWithDisabledChecks otherwise depending on whether every enabled check ran."
                derived_from = [Communication.E2EStatusReportingToApplication@1]
                version = 1
            }

            ScoreReq.CompReq SamplePtrExposesE2EResult {
                description = """{{SamplePtr}} shall provide an accessor that returns the {{E2EResult}} of the delivered sample, for every {{Event}} or {{Field}} that carries a configured E2E profile."""
                safety = ScoreReq.Asil.B
                derived_from = [Communication.E2EStatusReportingToApplication@1]
                version = 1
            }

            ScoreReq.CompReq E2EResultDeliveredRegardlessOfConsumerCriticality {
                description = """The {{E2EResult}} accessor on {{SamplePtr}} shall return a populated value for every consuming {{ProxyEvent}} or {{ProxyField}} instance of an {{Event}} or {{Field}} that carries a configured E2E profile, regardless of that consumer's own criticality level."""
                safety = ScoreReq.Asil.B
                note = "A QM consumer of an E2E-supervised event still receives a populated E2EResult by default and is free to ignore it; criticality alone shall not withhold the result (see [[PerConsumerE2ECheckOptOut]] for the only opt-out mechanism)."
                derived_from = [Communication.E2EStatusReportingToApplication@1, Communication.MixedCriticalityE2ESupervision@1]
                version = 1
            }

            ScoreReq.CompReq E2EResultFieldsReadDisabledWhenNotConfiguredOrOptedOut {
                description = """The {{E2EResult}} accessor on {{SamplePtr}} shall always return a value. When the delivering {{Event}} or {{Field}} carries no configured E2E profile, or when the consuming {{ProxyEvent}} or {{ProxyField}} instance has opted out of one or more checks (see [[PerConsumerE2ECheckOptOut]]), the corresponding {{E2EResult}} field(s) shall read {{kDisabled}} instead of the accessor returning no value."""
                safety = ScoreReq.Asil.B
                note = "This keeps the accessor free of an additional absent/optional return state, so a consumer can treat a not-configured element and a self-opted-out check the same way, by branching on kDisabled."
                derived_from = [Communication.E2EStatusReportingToApplication@1, Communication.MixedCriticalityE2ESupervision@1]
                version = 1
            }

            ScoreReq.CompReq E2EResultMutationRestrictedToCheckAndSupervisionLogic {
                description = """Only the binding's E2E check logic and the binding-independent E2E supervision logic shall be able to set the fields of the {{E2EResult}} carried by a {{SamplePtr}}."""
                safety = ScoreReq.Asil.B
                note = "The binding sets data_integrity/sequence as the direct outcome of CheckMessage(); the binding-independent supervision logic sets historical_health and the derived summary."
                derived_from = [Communication.E2EStatusReportingToApplication@1]
                version = 1
            }

            ScoreReq.CompReq E2EResultReadOnlyForApplication {
                description = """The consuming application shall only be able to read the {{E2EResult}} carried by a {{SamplePtr}}."""
                safety = ScoreReq.Asil.B
                derived_from = [Communication.E2EStatusReportingToApplication@1]
                version = 1
            }
            ScoreReq.CompReq GetNewSamplesCallbackSignatureUnchangedByE2E {
                description = """Enabling E2E supervision for an {{Event}} or {{Field}} shall not change the signature of the sample-delivery callback passed to {{GetNewSamples}}."""
                safety = ScoreReq.Asil.B
                derived_from = [Communication.E2EStatusReportingToApplication@1]
                version = 1
            }

        }

    }

}
